-- The containers of the IEs of TOY, in the form of those of the application protocols.

TOY-Containers {
iso (1) identified-organization (3) dod (6) internet (1) private (4) enterprise (1) toy (0) modules (3) toy-Containers (5) }

DEFINITIONS AUTOMATIC TAGS ::=

BEGIN

IMPORTS

	Criticality,
	Presence,
	PrivateIE-ID,
	ProtocolExtensionID,
	ProtocolIE-ID
FROM TOY-CommonDataTypes

	maxPrivateIEs,
	maxProtocolExtensions,
	maxProtocolIEs
FROM TOY-Constants;

TOY-PROTOCOL-IES ::= CLASS {
	&id				ProtocolIE-ID					UNIQUE,
	&criticality	Criticality,
	&Value,
	&presence		Presence
}
WITH SYNTAX {
	ID				&id
	CRITICALITY		&criticality
	TYPE			&Value
	PRESENCE		&presence
}

TOY-PROTOCOL-IES-PAIR ::= CLASS {
	&id					ProtocolIE-ID				UNIQUE,
	&firstCriticality	Criticality,
	&FirstValue,
	&secondCriticality	Criticality,
	&SecondValue,
	&presence			Presence
}
WITH SYNTAX {
	ID						&id
	FIRST CRITICALITY		&firstCriticality
	FIRST TYPE				&FirstValue
	SECOND CRITICALITY		&secondCriticality
	SECOND TYPE				&SecondValue
	PRESENCE				&presence
}

TOY-PROTOCOL-EXTENSION ::= CLASS {
	&id				ProtocolExtensionID			UNIQUE,
	&criticality	Criticality,
	&Extension,
	&presence		Presence
}
WITH SYNTAX {
	ID				&id
	CRITICALITY		&criticality
	EXTENSION		&Extension
	PRESENCE		&presence
}

TOY-PRIVATE-IES ::= CLASS {
	&id				PrivateIE-ID,
	&criticality	Criticality,
	&Value,
	&presence		Presence
}
WITH SYNTAX {
	ID				&id
	CRITICALITY		&criticality
	TYPE			&Value
	PRESENCE		&presence
}

ProtocolIE-Container {TOY-PROTOCOL-IES : IEsSetParam} ::=
	SEQUENCE (SIZE (0..maxProtocolIEs)) OF
	ProtocolIE-Field {{IEsSetParam}}

ProtocolIE-SingleContainer {TOY-PROTOCOL-IES : IEsSetParam} ::=
	ProtocolIE-Field {{IEsSetParam}}

ProtocolIE-Field {TOY-PROTOCOL-IES : IEsSetParam} ::= SEQUENCE {
	id				TOY-PROTOCOL-IES.&id				({IEsSetParam}),
	criticality		TOY-PROTOCOL-IES.&criticality		({IEsSetParam}{@id}),
	value			TOY-PROTOCOL-IES.&Value			({IEsSetParam}{@id})
}

ProtocolIE-ContainerPair {TOY-PROTOCOL-IES-PAIR : IEsSetParam} ::=
	SEQUENCE (SIZE (0..maxProtocolIEs)) OF
	ProtocolIE-FieldPair {{IEsSetParam}}

ProtocolIE-FieldPair {TOY-PROTOCOL-IES-PAIR : IEsSetParam} ::= SEQUENCE {
	id					TOY-PROTOCOL-IES-PAIR.&id					({IEsSetParam}),
	firstCriticality	TOY-PROTOCOL-IES-PAIR.&firstCriticality	({IEsSetParam}{@id}),
	firstValue			TOY-PROTOCOL-IES-PAIR.&FirstValue			({IEsSetParam}{@id}),
	secondCriticality	TOY-PROTOCOL-IES-PAIR.&secondCriticality	({IEsSetParam}{@id}),
	secondValue			TOY-PROTOCOL-IES-PAIR.&SecondValue			({IEsSetParam}{@id})
}

ProtocolIE-ContainerList {INTEGER : lowerBound, INTEGER : upperBound, TOY-PROTOCOL-IES : IEsSetParam} ::=
	SEQUENCE (SIZE (lowerBound..upperBound)) OF
	ProtocolIE-SingleContainer {{IEsSetParam}}

ProtocolIE-ContainerPairList {INTEGER : lowerBound, INTEGER : upperBound, TOY-PROTOCOL-IES-PAIR : IEsSetParam} ::=
	SEQUENCE (SIZE (lowerBound..upperBound)) OF
	ProtocolIE-ContainerPair {{IEsSetParam}}

ProtocolExtensionContainer {TOY-PROTOCOL-EXTENSION : ExtensionSetParam} ::=
	SEQUENCE (SIZE (1..maxProtocolExtensions)) OF
	ProtocolExtensionField {{ExtensionSetParam}}

ProtocolExtensionField {TOY-PROTOCOL-EXTENSION : ExtensionSetParam} ::= SEQUENCE {
	id					TOY-PROTOCOL-EXTENSION.&id				({ExtensionSetParam}),
	criticality			TOY-PROTOCOL-EXTENSION.&criticality	({ExtensionSetParam}{@id}),
	extensionValue		TOY-PROTOCOL-EXTENSION.&Extension		({ExtensionSetParam}{@id})
}

PrivateIE-Container {TOY-PRIVATE-IES : IEsSetParam } ::=
	SEQUENCE (SIZE (1..maxPrivateIEs)) OF
	PrivateIE-Field {{IEsSetParam}}

PrivateIE-Field {TOY-PRIVATE-IES : IEsSetParam} ::= SEQUENCE {
	id					TOY-PRIVATE-IES.&id				({IEsSetParam}),
	criticality			TOY-PRIVATE-IES.&criticality		({IEsSetParam}{@id}),
	value				TOY-PRIVATE-IES.&Value				({IEsSetParam}{@id})
}

END
