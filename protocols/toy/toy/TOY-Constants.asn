-- The constants of TOY: its procedure codes, its limits and the identifiers of its IEs.

TOY-Constants {
iso (1) identified-organization (3) dod (6) internet (1) private (4) enterprise (1)
toy (0) modules (3) toy-Constants (4) }

DEFINITIONS AUTOMATIC TAGS ::=

BEGIN

IMPORTS
	ProcedureCode,
	ProtocolIE-ID
FROM TOY-CommonDataTypes;

id-Setup									ProcedureCode ::= 1
id-Release									ProcedureCode ::= 2
id-ErrorIndication							ProcedureCode ::= 3
id-PrivateMessage							ProcedureCode ::= 4
id-Notification								ProcedureCode ::= 5

maxPrivateIEs								INTEGER ::= 65535
maxProtocolExtensions						INTEGER ::= 65535
maxProtocolIEs								INTEGER ::= 65535
maxnoofErrors								INTEGER ::= 256
maxnoofItems								INTEGER ::= 16
maxnoofTransfers							INTEGER ::= 8
maxnoofAreas								INTEGER ::= 16
maxnoofConnections							INTEGER ::= 65536

id-UE-Core-ID								ProtocolIE-ID ::= 10
id-UE-RAN-ID								ProtocolIE-ID ::= 11
id-UE-IDs									ProtocolIE-ID ::= 12
id-Cause									ProtocolIE-ID ::= 15
id-CriticalityDiagnostics					ProtocolIE-ID ::= 16
id-NodeName									ProtocolIE-ID ::= 20
id-SecurityKey								ProtocolIE-ID ::= 21
id-Items									ProtocolIE-ID ::= 22
id-Item										ProtocolIE-ID ::= 23
id-TransferList								ProtocolIE-ID ::= 24
id-Container								ProtocolIE-ID ::= 25
id-Areas									ProtocolIE-ID ::= 26
id-Algorithms								ProtocolIE-ID ::= 27
id-Counts									ProtocolIE-ID ::= 28
id-Tunnel									ProtocolIE-ID ::= 29
id-NAS-PDU									ProtocolIE-ID ::= 30
id-TransferKind								ProtocolIE-ID ::= 31
id-NodeID									ProtocolIE-ID ::= 32
id-SecurityContext							ProtocolIE-ID ::= 33
id-FailureTransfer							ProtocolIE-ID ::= 34
id-SetupTransfer							ProtocolIE-ID ::= 35
id-ExtensionIndex							ProtocolIE-ID ::= 40
id-ExtendedCause							ProtocolIE-ID ::= 41

END
